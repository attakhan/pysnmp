MY-MIB DEFINITIONS ::= BEGIN

IMPORTS
        OBJECT-TYPE, Integer32, NOTIFICATION-TYPE, enterprises , MODULE-IDENTITY
                     FROM SNMPv2-SMI
;

myMIB MODULE-IDENTITY
LAST-UPDATED
"202005100000Z"
ORGANIZATION
"AFINITI"
CONTACT-INFO
"email: support@afiniti.com"
DESCRIPTION
"Custom Example MIB"
REVISION
"202005100000Z"
DESCRIPTION
"First and hopefully not the final revision"
::= { enterprises 42 }

myCompany       OBJECT IDENTIFIER ::= {myMIB 1}


testCount OBJECT-TYPE
    SYNTAX Integer32
    MAX-ACCESS read-only
    STATUS current
    DESCRIPTION "A sample count of something."
    ::= {myCompany 1}

testDescription OBJECT-TYPE
    SYNTAX OCTET STRING
    MAX-ACCESS read-only
    STATUS current
    DESCRIPTION "A description of something"
    ::= {myCompany 2}

testTrap NOTIFICATION-TYPE
    STATUS current
    DESCRIPTION "Test notification"
    ::= {myCompany 3}

END
